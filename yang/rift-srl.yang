module rift-srl {
  yang-version 1.1;
  namespace "srlinux.dev/ndk/rift-srl";
  prefix "rift-srl";

  description
    "YANG module for the RIFT protocol NDK agent (RFC 9692)";

  revision "2026-04-07" {
    description "M6: Polish and documentation";
  }

  container rift {
    description
      "Root container for RIFT protocol agent";

    leaf admin-state {
      description "Administrative state of the RIFT agent";
      type enumeration {
        enum enable {
          description "Enable the RIFT agent";
        }
        enum disable {
          description "Disable the RIFT agent";
        }
      }
      default "enable";
    }

    leaf system-id {
      description "RIFT system identifier (unsigned 64-bit)";
      type uint64;
    }

    leaf level {
      description "Level of this node in the RIFT fabric (0=leaf)";
      type uint8 {
        range "0..24";
      }
      default "0";
    }

    leaf oper-state {
      description "Operational state of the RIFT agent";
      config false;
      type enumeration {
        enum up {
          description "Agent is running";
        }
        enum down {
          description "Agent is not running";
        }
      }
    }

    list interface {
      description "RIFT-enabled interfaces";
      key "name";

      leaf name {
        description "SR Linux interface name (e.g., ethernet-1/1)";
        type string;
      }

      container adjacency {
        description "LIE adjacency state for this interface";
        config false;

        leaf state {
          description "Adjacency FSM state";
          type enumeration {
            enum one-way {
              description "No valid LIE received from neighbor";
            }
            enum two-way {
              description "Valid LIE received, no reflection yet";
            }
            enum three-way {
              description "Full adjacency established";
            }
          }
        }

        leaf neighbor-system-id {
          description "Neighbor system identifier";
          type uint64;
        }

        leaf neighbor-level {
          description "Neighbor level in the fabric";
          type uint8;
        }

        leaf neighbor-address {
          description "Neighbor IPv4 address";
          type string;
        }
      }
    }

    leaf lsdb-summary {
      description "Summary of the link-state database (TIE entries)";
      config false;
      type string;
    }

    leaf rib-summary {
      description "Summary of routes computed by SPF";
      config false;
      type string;
    }

    leaf spf-runs {
      description "Number of SPF computations performed";
      config false;
      type uint64;
    }

    leaf adjacency-count {
      description "Number of adjacencies in three-way state";
      config false;
      type uint32;
    }

    leaf lsdb-tie-count {
      description "Number of TIEs in the link-state database";
      config false;
      type uint32;
    }

    leaf route-count {
      description "Number of routes computed by SPF";
      config false;
      type uint32;
    }

    leaf disaggregation-summary {
      description "Active positive disaggregation prefixes, or none";
      config false;
      type string;
    }
  }
}
